module subif-and-interface {

  namespace "http://example.com/subif-and-interface";
  prefix subif-and-interface;

  import ietf-inet-types {
    prefix inet;
  }
  import tailf-common {
    prefix tailf;
  }
  import tailf-ncs {
    prefix ncs;
  }

  description
    "Simple customer-facing service to aid in the deployment of a subif on a device";

  revision 2019-08-09 {
    description
      "Initial revision.";
  }

  augment /ncs:services {

  list subif-and-interface {
    tailf:info "Manage customer subinterfaces";
    description "Simple CFS service skeleton from ncs-make-service";

    key name;
    leaf name {
      tailf:info "Unique customer name";
      tailf:cli-allow-range;
      type string;
    }

    leaf-list device {
      type leafref {
        path "/ncs:devices/ncs:device/ncs:name";
        }
      }

//    leaf interface-type {
//      tailf:info "Interface to which tail is applied";
//      type enumeration {
//        enum "FastEthernet";
//        enum "GigabitEthernet";
//        enum "TenGigE";
//      }
//    }

    leaf interface-num {
      tailf:info "Interface number facing customer";
        type string;
    }

    leaf subif-num {
      tailf:info "Subinterface number for customer tail; must match VLAN";
      type uint16 {
        range "1..4095";
      }
    }

    leaf ip-address {
      tailf:info "Interface IP address";
      type inet:ipv4-address;
    }

    leaf mask {
      tailf:info "Interface subnet mask";
      type inet:ipv4-address;
    }

    uses ncs:service-data;
    ncs:servicepoint "subif-and-interface";

  }
}
}
